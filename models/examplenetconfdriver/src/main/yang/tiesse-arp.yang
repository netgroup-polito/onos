module tiesse-arp {

    namespace "urn:ietf:params:xml:ns:yang:tiesse-arp";
    prefix "tiesse-arp";
    import tiesse-cli {
	prefix cli;
    }
    organization "tiesse";

    description
        "This module is the YANG module for Tiesse Arp protocol.";

    revision "2017-05-29" {
        description "Initial revision.";
    }

    typedef local-proxy-arp-in-type {
        type enumeration {
            enum no-restricted {
                value 0;
                description "Reply for any local target IP address configured on any interface (default)";
            }
            enum ifc-restricted {
                value 1;
                description "Reply only if the target IP address is local address configured on the incoming interface";
            }
            enum net-restricted {
                value 2;
                description "Reply only if the target IP address is local address configured on the incoming interface and both with the sender's IP address are part from same subnet on this interface";
            }
        }
    }

    typedef local-proxy-arp-out-type {
        type enumeration {
            enum no-restricted {
                value 0;
                description "Use any local address, configured on any interface";
            }
            enum addr-restricted {
                value 1;
                description "Try to avoid local addresses that are not in the target's subnet for this interface. If there is no such subnet it selects source address according to the rules for level 2";
            }
            enum best-addr-restricted {
                value 2;
                description "Always use the best local address for this target";
            }
        }
    }

    grouping arp-params {
        leaf arp-timeout {
            type uint32;
            default 30;
            description "Configure average expiration time for an arp cache entry";
            cli:immediate;
        }
        leaf local-proxy-arp-in {
            type local-proxy-arp-in-type;
            description "Configure different modes for sending replies in response to received ARP requests that resolve local target IP addresses";
            cli:immediate;
        }
        leaf local-proxy-arp-out {
            type local-proxy-arp-out-type;
            description "Configure different restriction levels for announcing the local source IP address from IP packets in ARP requests sent on this interface";
            cli:immediate;
        }
        leaf proxy-arp {
            type empty;
            description "Enable proxy-arp|Disable proxy-arp";
        }
    }
}
