module tiesse-bridge {
    namespace "urn:ietf:params:xml:ns:yang:tiesse-bridge";
    prefix "bridge";

    import tiesse-cli {
        prefix cli;
    }

    import tiesse-ip {
        prefix ip;
    }

    description "tiesse-bridge module";
    contact "f.antonini@tiesse.com";

    revision "2017-02-25" {
        description "Removed augmentation";
    }

    revision "2016-10-03" {
        description
            "Initial revision.";
    }

    rpc save {
        output {
            leaf result {
                type cli:enum_result;
            }
        }
    }

    rpc reload {
        output {
            leaf result {
                type cli:enum_result;
            }
        }
    }

    container "bridge" {
            list br {
                key name;
                leaf name {
                    type string{
                    pattern "(br0|br1|br2|br3|br4|br5|br6|br7)";
                }
                    description "Set bridge name";
                }
                list interface {
                    key name;
                    leaf name {
                        type string;
                    }
                }
		uses ip:ip-params;
                leaf active {
                    type cli:onoff;
                    default "on";
                }
                cli:hidden;
        }
        description "bridge container";
    }
}
