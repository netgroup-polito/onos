module tiesse-vlan {
    namespace "urn:ietf:params:xml:ns:yang:tiesse-vlan";
    prefix "vlan";

    import tiesse-cli {
        prefix cli;
    }

    import ietf-yang-types {
        prefix yang;
    }

    import tiesse-ip {
        prefix ip;
    }

    import tiesse-arp {
        prefix arp;
    }

    description "tiesse-vlan module";
    contact "f.antonini@tiesse.com";

    revision "2017-02-25" {
        description "Removed augmentation";
    }

    revision "2016-10-03" {
        description
            "Initial revision.";
    }

    grouping vlan-params {
        leaf protocol {
            type string {
                pattern '(802.1ad|802.1q)';
            }
            description "Configure vlan protocol";
        }
        leaf mac-address {
            type yang:mac-address;
            description "Configure mac-address|Unconfigure mac-address";
        }
        uses ip:ip-params;
        uses arp:arp-params;
        list map-to-cos {
            key "cos";
            leaf cos {
                type uint32{
                 range "0..7";
                }
            }
            leaf class-id {
                type string;
            }
            leaf dscp {
                type uint32{
                 range "0..63";
                }
            }
        description "Configure class of service|Unconfigure class of service";
        }
        leaf rx-untagged {
            type empty;
            description "Notify that Received Packets are Untagged|UnConfigure Notify that Received Packets are Untagged";
        }
        leaf description {
            type string;
            description "Configure vlan description - Unconfigure vlan description";
        }
        leaf masquerade {
            type empty;
            description "Enable Masquerade (NAT)|Disable Masquerade (NAT)";
        }
        leaf training {
            type string{
                pattern "(active|disable|enable)";
            }
        description "Configure training|Unconfigure training";
        }
        leaf dhcp-client {
            type empty;
            description "Enable dhcp-client|Disable dhcp-client";
        }
        leaf status {
            type string;
            config false;
        }
    }

    container "vlan" {
        list vlans {
            key "vid interface";
            leaf vid {
                type uint32 {
                    range "0..4095";
                }
                description "Configure vlan number";
            }
            leaf interface {
                type cli:ts-interfaces;
                description "physical interface";
            }
            uses vlan-params;
	    leaf active {
                type cli:onoff;
                default "off";
            }
            description "[new] Vlan list";
            cli:hidden;
        }
        description "vlan container";
    }
}
