module tiesse-ip {

    namespace "urn:ietf:params:xml:ns:yang:tiesse-ip";
    prefix "tiesse-ip";

    import ietf-inet-types {
        prefix inet;
    }

    import tiesse-cli {
        prefix cli;
    }

    organization "tiesse";

    description
        "This module is the YANG module for Tiesse Ip stack.";

    revision "2017-05-21" {
        description "Initial revision.";
    }

    typedef netmask {
        type string {
            pattern '(((255\.){3}(255|254|252|248|240|224|192|128|0+))|((255\.){2}(255|254|252|248|240|224|192|128|0+)\.0)|((255\.)(255|254|252|248|240|224|192|128|0+)(\.0+){2})|((255|254|252|248|240|224|192|128|0+)(\.0+){3}))';
        }
    }
    typedef ipv4-address {
        type union {
            type inet:ipv4-address-no-zone;
            type inet:ipv4-prefix;
        }
    }

    grouping ip-params {
        leaf ipaddr {
            type ipv4-address;
            description
                "Configure ip address - IP address (a.b.c.d)|Unconfigure ip address";
            cli:group "1";
        }
        leaf ipv6addr {
            type inet:ipv6-address-no-zone;
            description
                "Configure ipv6 address - IPv6 address (X:X::X:X)|Unconfigure ipv6 address";
        }
        leaf netmask {
            when 're-match(../ipaddr, ".*/.*") = 0';
            type netmask;
            description
                "Netmask to be configured when ipaddr is not an ip-prefix - Netmask (a.b.c.d)";
            cli:group "1";
        }
        leaf broadcast {
            type ipv4-address;
            description
                "Configure broadcast ip address - IP address (a.b.c.d)|Unconfigure broadcast ip address";
            cli:group "1";
        }
        leaf mtu {
            type uint16 {
                range "68..max";
            }
            units "octets";
            description
                "Configure Maximum Transmission Unit";
            cli:group "1";
        }
        leaf qlen {
            type uint32;
            description "Configure interface queue length|Unconfigure interface queue length";
        }
        leaf bandwidth {
            type uint32;
            description "Configure interface bandwidth - kbit/s|Unconfigure interface bandwidth";
        }
    }

    container ip;
}
