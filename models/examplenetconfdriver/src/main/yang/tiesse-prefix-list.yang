module tiesse-prefix-list {

    namespace "urn:ietf:params:xml:ns:yang:tiesse-prefix-list";
    prefix "pfxlst";

    import ietf-inet-types {
        prefix inet;
    }

    import tiesse-cli {
        prefix cli;
    }

    description "tiesse-prefix-list module";
    contact "f.antonini@tiesse.com";

    revision "2017-07-07" {
        description
            "Initial revision.";
    }

    grouping prefix-list-ipv4-group {
        list prefix-list {
            key name;
            leaf name {
                type string;
            }
            leaf-list description {
                type string;
                cli:reinit;
            }
            list seq {
                key 'id policy ipaddr';
                leaf id {
                    type uint16;
                    cli:hidden;
                }
                leaf policy {
                    type cli:acl-deny-permit;
                    cli:hidden;
                }
                leaf ipaddr {
                    type union {
                        type inet:ipv4-prefix;
                        type enumeration {
                            enum any;
                        }
                    }
                    cli:hidden;
                }
                leaf ge {
                    type uint8 {
                        range "0..32";
                    }
                    cli:group "1";
                    // fixme: vedi ticket #65, le foglie ge ed le devono essere gestire a consumo
                    // se si usa il cli:group il reinit non funziona se si asserisce le e poi lo si rimuove con ge sempre presente
                    // fixme: mettere delle condizioni must sui valori ammessi per ge e le
                }
                leaf le {
                    type uint8 {
                        range "0..32";
                    }
                    cli:group "1";
                    // fixme: vedi ticket #65, le foglie ge ed le devono essere gestire a consumo
                    // se si usa il cli:group il reinit non funziona se si asserisce le e poi lo si rimuove con ge sempre presente
                    // fixme: mettere delle condizioni must sui valori ammessi per ge e le
                }
                cli:showdeeper;
                cli:reinit;
            }
            description '[new|noexec]';
        } // prefix-list
    } // grouping ipv4
    
    grouping prefix-list-ipv6-group {
        list prefix-list {
            key name;
            leaf name {
                type string;
            }
            list seq {
                key 'id policy ipaddr';
                leaf id {
                    type uint16;
                    cli:hidden;
                }
                leaf policy {
                    type cli:acl-deny-permit;
                    cli:hidden;
                }
                leaf ipaddr {
                    type union {
                        type inet:ipv6-address-no-zone;
                        type enumeration {
                            enum any;
                        }
                    }
                    cli:hidden;
                }
                leaf ge {
                    type uint8 {
                        range "0..32";
                    }
                    cli:group "1";
                    // fixme: vedi ticket #65, le foglie ge ed le devono essere gestire a consumo
                    // se si usa il cli:group il reinit non funziona se si asserisce le e poi lo si rimuove con ge sempre presente
                    // fixme: mettere delle condizioni must sui valori ammessi per ge e le
                }
                leaf le {
                    type uint8 {
                        range "0..32";
                    }
                    cli:group "1";
                    // fixme: vedi ticket #65, le foglie ge ed le devono essere gestire a consumo
                    // se si usa il cli:group il reinit non funziona se si asserisce le e poi lo si rimuove con ge sempre presente
                    // fixme: mettere delle condizioni must sui valori ammessi per ge e le
                }
                cli:showdeeper;
                cli:reinit;
            }
            description '[new|noexec]';
        } // prefix-list
    } // grouping ipv6
}
