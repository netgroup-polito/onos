module tiesse-access-list {

    namespace "urn:ietf:params:xml:ns:yang:tiesse-access-list";
    prefix "acl";

    import ietf-inet-types {
        prefix inet;
    }

    import tiesse-cli {
        prefix cli;
    }

    description "tiesse-access-list module";
    contact "f.antonini@tiesse.com";

    revision "2017-07-07" {
        description
            "Initial revision.";
    }

    typedef word {
        type string;
    }

    typedef acl-id {
        type union {
            type word;
            type uint16 {
                range "1..99 | 100..199 | 1300..1999 | 2000..2699";
            }
        }
    }

    typedef acl-any-type {
        type string {
            pattern 'any any|any host (([0-9]|[1-9][0-9]|1[0-9][0-9]|2[0-4][0-9]|25[0-5])\.){3}([0-9]|[1-9][0-9]|1[0-9][0-9]|2[0-4][0-9]|25[0-5])(%[\p{N}\p{L}]+)?|any(\s(([0-9]|[1-9][0-9]|1[0-9][0-9]|2[0-4][0-9]|25[0-5])\.){3}([0-9]|[1-9][0-9]|1[0-9][0-9]|2[0-4][0-9]|25[0-5])(%[\p{N}\p{L}]+)?){2}';
        }
        description 'any any| any host IPADDRESS|any IPADDRESS IPADDRESS';
    }

    typedef acl-ipaddr-type {
        type string {
            pattern '(([0-9]|[1-9][0-9]|1[0-9][0-9]|2[0-4][0-9]|25[0-5])\.){3}([0-9]|[1-9][0-9]|1[0-9][0-9]|2[0-4][0-9]|25[0-5])(%[\p{N}\p{L}]+)?(\s(([0-9]|[1-9][0-9]|1[0-9][0-9]|2[0-4][0-9]|25[0-5])\.){3}([0-9]|[1-9][0-9]|1[0-9][0-9]|2[0-4][0-9]|25[0-5])(%[\p{N}\p{L}]+)?){3}|(([0-9]|[1-9][0-9]|1[0-9][0-9]|2[0-4][0-9]|25[0-5])\.){3}([0-9]|[1-9][0-9]|1[0-9][0-9]|2[0-4][0-9]|25[0-5])(%[\p{N}\p{L}]+)?(\s(([0-9]|[1-9][0-9]|1[0-9][0-9]|2[0-4][0-9]|25[0-5])\.){3}([0-9]|[1-9][0-9]|1[0-9][0-9]|2[0-4][0-9]|25[0-5])(%[\p{N}\p{L}]+)?){1} any|(([0-9]|[1-9][0-9]|1[0-9][0-9]|2[0-4][0-9]|25[0-5])\.){3}([0-9]|[1-9][0-9]|1[0-9][0-9]|2[0-4][0-9]|25[0-5])(%[\p{N}\p{L}]+)?(\s(([0-9]|[1-9][0-9]|1[0-9][0-9]|2[0-4][0-9]|25[0-5])\.){3}([0-9]|[1-9][0-9]|1[0-9][0-9]|2[0-4][0-9]|25[0-5])(%[\p{N}\p{L}]+)?){1} host (([0-9]|[1-9][0-9]|1[0-9][0-9]|2[0-4][0-9]|25[0-5])\.){3}([0-9]|[1-9][0-9]|1[0-9][0-9]|2[0-4][0-9]|25[0-5])(%[\p{N}\p{L}]+)?';
        }
    }

    typedef acl-host-type {
        type string {
            pattern '(([0-9]|[1-9][0-9]|1[0-9][0-9]|2[0-4][0-9]|25[0-5])\.){3}([0-9]|[1-9][0-9]|1[0-9][0-9]|2[0-4][0-9]|25[0-5])(%[\p{N}\p{L}]+)?(\s(([0-9]|[1-9][0-9]|1[0-9][0-9]|2[0-4][0-9]|25[0-5])\.){3}([0-9]|[1-9][0-9]|1[0-9][0-9]|2[0-4][0-9]|25[0-5])(%[\p{N}\p{L}]+)?){2}|(([0-9]|[1-9][0-9]|1[0-9][0-9]|2[0-4][0-9]|25[0-5])\.){3}([0-9]|[1-9][0-9]|1[0-9][0-9]|2[0-4][0-9]|25[0-5])(%[\p{N}\p{L}]+)? any|(([0-9]|[1-9][0-9]|1[0-9][0-9]|2[0-4][0-9]|25[0-5])\.){3}([0-9]|[1-9][0-9]|1[0-9][0-9]|2[0-4][0-9]|25[0-5])(%[\p{N}\p{L}]+)? host (([0-9]|[1-9][0-9]|1[0-9][0-9]|2[0-4][0-9]|25[0-5])\.){3}([0-9]|[1-9][0-9]|1[0-9][0-9]|2[0-4][0-9]|25[0-5])(%[\p{N}\p{L}]+)?';
        }
    }

    grouping access-list-group {
        list access-list {
            must 'count(current()/*) > 2' {
                error-message "at least one leaf must be set!";
            }
            key 'id policy';
            leaf id {
                type acl-id;
                description "acl identifier";
                cli:hidden;
            }
            leaf policy {
                type cli:acl-deny-permit;
                cli:hidden;
            }
            list ipadd {
                when "(../id <= 99 and ../id >= 1) or (../id <= 1999 and ../id >= 1300)";
                key ip;
                leaf ip {
                    type union {
                        type string {
                            pattern '(([0-9]|[1-9][0-9]|1[0-9][0-9]|2[0-4][0-9]|25[0-5])\.){3}([0-9]|[1-9][0-9]|1[0-9][0-9]|2[0-4][0-9]|25[0-5])(%[\p{N}\p{L}]+)?(\s?(([0-9]|[1-9][0-9]|1[0-9][0-9]|2[0-4][0-9]|25[0-5])\.){3}([0-9]|[1-9][0-9]|1[0-9][0-9]|2[0-4][0-9]|25[0-5])(%[\p{N}\p{L}]+)?){0,1}';
                        }
                        type enumeration {
                            enum any;
                        }
                    }
                }
                cli:hidden;
                // fixme: la presenza di due liste hidden ipadd e word crea problemi perchè la yangcli non sa da che parte andare, vedi ticket #100
            }
            container host {
                when "(../id <= 99 and ../id >= 1) or (../id <= 1999 and ../id >= 1300)";
                list ipadd {
                    key ip;
                    leaf ip {
                        //when "(../id <= 99 and ../id >= 1) or (../id <= 1999 and ../id >= 1300)";
                        type union {
                            type string {
                                pattern '(([0-9]|[1-9][0-9]|1[0-9][0-9]|2[0-4][0-9]|25[0-5])\.){3}([0-9]|[1-9][0-9]|1[0-9][0-9]|2[0-4][0-9]|25[0-5])(%[\p{N}\p{L}]+)?(\s?(([0-9]|[1-9][0-9]|1[0-9][0-9]|2[0-4][0-9]|25[0-5])\.){3}([0-9]|[1-9][0-9]|1[0-9][0-9]|2[0-4][0-9]|25[0-5])(%[\p{N}\p{L}]+)?){0,1}';
                            }
                            type enumeration {
                                enum any;
                            }
                        }
                        //cli:hidden;
                    }
                    cli:hidden;
                }
            }
            container ip {
                when "(../id <= 199 and ../id >= 100) or (../id <= 2699 and ../id >= 2000)";
                list ipadd {
                    key ip;
                    leaf ip {
                        type union {
                            type acl-any-type;
                            type acl-ipaddr-type;
                        }
                    }
                    cli:hidden;
                }
                container host {
                    when "(../../id <= 99 and ../../id >= 1) or (../../id <= 1999 and ../../id >= 1300)";
                    list ipadd {
                        key ip;
                        leaf ip {
                            type acl-host-type;
                        }
                        cli:hidden;
                    }
                }
                //cli:group "1";
                // fixme: il container 'ip' dovrebbe essere visibile solo se l'id appartiene al range specificato nel when
                // attualmente invece viene mostrato subito in parallelo alle altre foglie, vedi ticket #98
            }
            list word {
                when "not ((../id <= 199 and ../id >= 100) or (../id <= 2699 and ../id >= 2000))";
                key ipaddr;
                leaf ipaddr {
                    type inet:ipv4-prefix;
                }
                leaf exact-match {
                    type empty;
                }
                cli:hidden;
            }
            description "[noexec]access list";
            // fixme: la presenza di due liste hidden ipadd e word crea problemi perchè la yangcli non sa da che parte andare, vedi ticket #100
        }
    }
}
